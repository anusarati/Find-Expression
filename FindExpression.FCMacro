# 0-BSD
import re
from time import time_ns
# thanks to Gaël Ecorchard for https://wiki.freecad.org/Macro_MessageBox
from PySide2 import QtCore
from PySide2.QtWidgets import QWidget, QInputDialog, QMessageBox

def getObjectPath(object):
    hierarchy = [object.Label]
    # add containers
    while bool(object.InList):
        object = object.InList[0]
        hierarchy.append(object.Label)
    return ".".join([str(object) for object in reversed(hierarchy)])
        

def bracket(name):
    """Add <<>> brackets to a name"""
    return re.sub(r"^(?<!<<)([^<>.]+)(?!>>)", r"<<\1>>", name)

def unbracket(name):
    """Remove <<>> brackets from a name"""
    return re.sub(r"^<<([^<>.]+)>>", r"\1", name)

def findExpressionInSpreadsheet(spreadsheet, name, matches):
    basePath = getObjectPath(spreadsheet) + "."
    name = unbracket(name)
    baseObjectMatch = re.match(r"[^.]+", name)
    baseObject = baseObjectMatch.group()

    # doesn't account for spreadsheets labeled with the name of another
    if baseObject in [spreadsheet.Name, spreadsheet.Label]:
        name = name[baseObjectMatch.end() + 1:]

    nameRegex = re.escape(name)
    for propertyName in spreadsheet.PropertiesList:
        # get cell names
        if re.fullmatch(r"[A-Z]\d+", propertyName):
            content = spreadsheet.getContents(propertyName)
            if content[0] == "=" and re.search(nameRegex, unbracket(content)):
                matches.append(basePath + propertyName)

    return matches


def updateMatches(matches, object, name):
    if object.TypeId == "Spreadsheet::Sheet":
        findExpressionInSpreadsheet(object, name, matches)
    else:
        findExpressionIn(object, name, matches)


def findExpressionIn(object, name, matches):
    for expression in object.ExpressionEngine:
        if expression[1] == name:
            matches.append(getObjectPath(object) + "." + expression[0])
    return matches
            

def findExpression(name):
    matches = []
    for object in App.ActiveDocument.Objects:
        updateMatches(matches, object, name)
    return matches

widget = QWidget()
dialog = QInputDialog()

expressionName = dialog.getText(widget, "Find expression", "Enter an expression")[0]

# add brackets
expressionName = bracket(expressionName)

time0 = time_ns()

matches = findExpression(expressionName)

timeTaken = (time_ns() - time0) / 1e9
print(f"Search completed in {timeTaken} seconds")

result = "\n".join(matches) if matches else "Expression not found."

messageBox = QMessageBox()
messageBox.setTextInteractionFlags(QtCore.Qt.TextSelectableByMouse)
messageBox.setText(result)
messageBox.exec_()
